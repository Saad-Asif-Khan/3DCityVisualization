FME workspace ConversionModel.fmw

Parameters:
- SourceDataset_CITYGML = ""D:\HFT Course Material\Sem 2\GSS\opencitymodel-master\Data\data download test\Alaska\Alaska-02020-000.zip" "D:\HFT Course Material\Sem 2\GSS\opencitymodel-master\Data\data download test\Alaska\Alaska-02020-001.zip" "D:\HFT Course Material\Sem 2\GSS\opencitymodel-master\Data\data download test\Alaska\Alaska-02090-000.zip" "D:\HFT Course Material\Sem 2\GSS\opencitymodel-master\Data\data download test\Alaska\Alaska-02105-000.zip" "D:\HFT Course Material\Sem 2\GSS\opencitymodel-master\Data\data download test\Alaska\Alaska-02110-000.zip" "D:\HFT Course Material\Sem 2\GSS\opencitymodel-master\Data\data download test\Alaska\Alaska-02170-000.zip""   # Source CityGML File(s)
- DestDataset_CESIUM3DTILES = C:\Users\Standard-User\Desktop\Alaska   # Destination Cesium 3D Tiles Folder

Readers:
- CITYGML_1: CITYGML from $(SourceDataset_CITYGML) in EPSG:4979

Writers:
- CESIUM3DTILES_1: CESIUM3DTILES to $(DestDataset_CESIUM3DTILES)

CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
    -> CoordinateSwapper
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, area xml_buffer, county xml_buffer, fp_source xml_buffer, height_source xml_buffer, latitude xml_buffer, longitude xml_buffer, mgrs xml_buffer, state xml_buffer, ubid xml_buffer
    -> CoordinateSwapper
CoordinateSwapper
    SWAP_TYPE = X <-> Y
    -> GeometryValidator
GeometryValidator
    ISSUE_ATTR_NAME = _issues
    PRESETS = Custom
    REPAIR = Yes
    RULES = SHELL_VALIDATION FLIP_APPEARANCE_MODE]FLIP_APPEARANCES]FME_CONTROLLER_QUERY_FILE]transformers/dependencies/geometryvalidator/SHELL_VALIDATION.fme
    SUMMARY = Detailed
    PASSED -> tileset (writer CESIUM3DTILES_1)
    FAILED -> AttributeFileWriter
    REPAIRED -> tileset (writer CESIUM3DTILES_1)
AttributeFileWriter
    CHAR_ENCODING = fme-system
    OVERWRITE_FILE = Overwrite file
tileset (writer CESIUM3DTILES_1)
    attributes: citygml_measured_height float, citygml_measured_height_units string, citygml_level_of_detail{} string, area string, county string, fp_source string, height_source string, latitude string, longitude string, mgrs string, state string, ubid string, _issues{}.count string, _issues{}.issue_found string, _issues{}.location_sample.x string, _issues{}.location_sample.y string, _issues{}.location_sample.z string
